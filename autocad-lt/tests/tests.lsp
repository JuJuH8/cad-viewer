;; SPDX-License-Identifier: GPL-3.0-or-later
;;; Tests de « Traitement de plans » : à charger après TraitementPlans.lsp sur un dessin vide
;;; (voir run_tests.py). Chaque vérification affiche « CV-RES=OK nom » ou « CV-RES=ECHEC nom ».

(setq tt:*ok* 0 tt:*ko* 0)

;; Profils des tests dans un dossier temporaire (le dossier réel de l'utilisateur n'est pas touché).
(setq tt:*dir* (strcat (getenv "TEMP") "\\tp_tests_profils"))
(vl-mkdir tt:*dir*)
(foreach f (vl-directory-files tt:*dir* "*.tpp" 1) (vl-file-delete (strcat tt:*dir* "\\" f)))
(defun tp:dir () tt:*dir*)

(defun tt:check (name c)
  (if c
    (progn (setq tt:*ok* (1+ tt:*ok*)) (princ (strcat "\nCV-RES=OK " name)))
    (progn (setq tt:*ko* (1+ tt:*ko*)) (princ (strcat "\nCV-RES=ECHEC " name)))))

(defun tt:test (name fn / r)
  (tt:reset)
  (setq r (vl-catch-all-apply fn))
  (if (vl-catch-all-error-p r)
    (progn (setq tt:*ko* (1+ tt:*ko*))
           (princ (strcat "\nCV-RES=ECHEC " name " : erreur " (vl-catch-all-error-message r))))))

;; Réglages : toutes les opérations désactivées sauf keys, puis paramètres extra.
(defun tt:cfg (keys extra / cfg)
  (setq cfg (tp:defaults))
  (foreach k tp:*ops* (setq cfg (tp:cfg-set cfg k (if (member k keys) T nil))))
  (foreach p extra (setq cfg (tp:cfg-set cfg (car p) (cdr p))))
  cfg)

(defun tt:run (keys extra) (setq tt:*report* (tp:run (tt:cfg keys extra))))

(defun tt:reset (/ ss)
  (tp:layers-free)
  (setvar "TILEMODE" 1)
  (if (setq ss (ssget "_X")) (command "_.ERASE" ss ""))
  (repeat 3 (command "_.-PURGE" "_A" "*" "_N") (tp:end-cmd))
  (setvar "INSUNITS" 4))

(defun tt:layer (name color flags lt)
  (entmake (list '(0 . "LAYER") '(100 . "AcDbSymbolTableRecord") '(100 . "AcDbLayerTableRecord")
                 (cons 2 name) (cons 70 flags) (cons 62 color) (cons 6 (if lt lt "Continuous")))))

(defun tt:line (p1 p2 extra) (entmake (append (list '(0 . "LINE") '(8 . "0") (cons 10 p1) (cons 11 p2)) extra)) (entlast))
(defun tt:text (s p extra) (entmake (append (list '(0 . "TEXT") '(8 . "0") (cons 10 p) '(40 . 2.5) (cons 1 s)) extra)) (entlast))
(defun tt:mtext (s p extra)
  (entmake (append (list '(0 . "MTEXT") '(100 . "AcDbEntity") '(8 . "0") '(100 . "AcDbMText") (cons 10 p) '(40 . 2.5) (cons 1 s)) extra))
  (entlast))
(defun tt:lwpoly (pts closed extra)
  (entmake (append (list '(0 . "LWPOLYLINE") '(100 . "AcDbEntity") '(8 . "0") '(100 . "AcDbPolyline")
                         (cons 90 (length pts)) (cons 70 (if closed 1 0)))
                   (mapcar '(lambda (p) (cons 10 p)) pts) extra))
  (entlast))

(defun tt:all (/ ss i r)
  (if (setq ss (ssget "_X"))
    (progn (setq i 0) (repeat (sslength ss) (setq r (cons (entget (ssname ss i) '("*")) r) i (1+ i)))))
  (reverse r))
(defun tt:of-type (typ) (vl-remove-if-not '(lambda (d) (= typ (tp:dxf 0 d))) (tt:all)))
(defun tt:count (typ) (length (tt:of-type typ)))
(defun tt:block-lists (name / e r)
  (setq e (entnext (tblobjname "BLOCK" name)))
  (while e (setq r (cons (entget e '("*")) r) e (entnext e)))
  (reverse r))
(defun tt:block-types (name) (mapcar '(lambda (d) (tp:dxf 0 d)) (tt:block-lists name)))
(defun tt:layer-flags (name) (tp:dxf 70 (tblsearch "LAYER" name)))
(defun tt:layer-color (name) (tp:dxf 62 (tblsearch "LAYER" name)))
(defun tt:near (a b) (equal a b 1e-6))

(defun tt:block (name ents / ok)
  (entmake (list '(0 . "BLOCK") (cons 2 name) '(70 . 0) '(10 0.0 0.0 0.0)))
  (foreach d ents (entmake d))
  (entmake '((0 . "ENDBLK"))))

(defun tt:insert (name p extra) (entmake (append (list '(0 . "INSERT") (cons 2 name) '(8 . "0") (cons 10 p)) extra)) (entlast))

;;; ---------------------------------------------------------------- outils

(defun tt:rep (s n / r) (setq r "") (repeat n (setq r (strcat r s))) r)

(tt:test "unformat"
  '(lambda ()
     (tt:check "mtext : formatage retiré"
               (= (tp:mt-unformat "{\\C1;\\fArial|b1;Bonjour} \\Pmonde \\S1^2;" tp:*fmt-all* T) "Bonjour \\Pmonde 1/2"))
     (tt:check "mtext : couleurs seules retirées"
               (= (tp:mt-unformat "{\\C1;\\fArial;A}\\c255;B" '(67 99) nil) "{\\fArial;A}B"))
     (tt:check "mtext : échappements conservés" (= (tp:mt-unformat "a\\\\b\\{c\\}" tp:*fmt-all* T) "a\\\\b\\{c\\}"))
     (tt:check "mtext : rognage" (= (tp:mt-trim " \\P\\Pabc def\\P ") "abc def"))
     (tt:check "mtext : vide" (= "" (tp:trim (tp:mt-plain "{\\fArial;  }\\P"))))
     (tt:check "mt-set : découpage 250" (= 600 (strlen (tp:mt-get (tp:mt-set '((0 . "MTEXT") (1 . "x")) (tt:rep "a" 600))))))
     (tt:check "csv : découpage" (equal (tp:csv-split "a;\"b;c\";\"d\"\"e\"" ";") '("a" "b;c" "d\"e")))
     (tt:check "wc : échappement" (wcmatch "A-MUR#1" (tp:wc-escape "A-MUR#1")))
     (tt:check "source avec *" (and (tp:src-match "A-MUR.Porteur" "a-mur*") (not (tp:src-match "B-MUR" "A-MUR*"))))
     (tt:check "source exacte" (and (tp:src-match "Mur #1" "MUR #1") (not (tp:src-match "Mur #12" "Mur #1"))))
     (tt:check "longueur arc de polyligne" (tt:near (tp:seg-len '(0.0 0.0) '(2.0 0.0) 1.0) pi))))


(tt:test "profils"
  '(lambda (/ cfg back)
     (setq cfg (tp:cfg-set (tt:cfg '("APLATIR") nil) "CALQUES_FILTRE" '("MOB*" "Équipé")))
     (setq cfg (tp:cfg-set cfg "COUL_TABLE" '((1 . 3) (256 . 8))))
     (setq cfg (tp:cfg-set cfg "TABLE_CALQUES" "C:\\Données\\table.csv"))
     (tp:profile-write "Essai été" cfg)
     (setq back (tp:profile-read "Essai été"))
     (tt:check "profil relu à l'identique" (equal (vl-sort cfg '(lambda (a b) (< (car a) (car b))))
                                                   (vl-sort back '(lambda (a b) (< (car a) (car b))))))
     (vl-file-delete (tp:profile-file "Essai été"))
     (tp:ensure-profiles)
     (tt:check "profils fournis" (and (member "Express" (tp:profile-names)) (member "Base architecte" (tp:profile-names))
                                      (member "Fond de plan gris" (tp:profile-names))))
     (tt:check "profil absent : défauts" (equal (tp:profile-load "nexistepas") (tp:defaults)))))

;;; ---------------------------------------------------------------- calques

(tt:test "liberer"
  '(lambda ()
     (tt:layer "GEL" 1 1 nil) (tt:layer "VERR" 2 4 nil) (tt:layer "ETEINT" -3 0 nil)
     (tt:run '("LIBERER") nil)
     (tt:check "calques dégelés, déverrouillés" (and (= 0 (logand 5 (tt:layer-flags "GEL"))) (= 0 (logand 5 (tt:layer-flags "VERR")))))
     (tt:check "calque rallumé" (= 3 (tt:layer-color "ETEINT")))
     (tt:check "calque 0 courant" (= "0" (getvar "CLAYER")))))

(tt:test "etats retablis"
  '(lambda (/ e1 e2)
     (tt:layer "VERR" 2 4 nil) (tt:layer "ETEINT" -3 0 nil)
     (setq e1 (tt:line '(0.0 0.0 0.0) '(10.0 0.0 0.0) '((8 . "VERR") (62 . 1))))
     (setq e2 (tt:line '(0.0 5.0 0.0) '(10.0 5.0 0.0) '((8 . "ETEINT") (62 . 1))))
     (tt:run '("DUCALQUE") '(("VERROUILLES") ("DESACTIVES" . T)))
     (tt:check "calque verrouillé rétabli" (= 4 (logand 4 (tt:layer-flags "VERR"))))
     (tt:check "calque éteint rétabli" (= -3 (tt:layer-color "ETEINT")))
     (tt:check "objet du calque verrouillé non traité" (= 1 (tp:dxf 62 (entget e1))))
     (tt:check "objet du calque éteint traité" (null (tp:dxf 62 (entget e2))))))

(tt:test "suppression de calques"
  '(lambda ()
     (tt:layer "MOBILIER" 4 0 nil) (tt:layer "MURS" 1 0 nil)
     (tt:line '(0.0 0.0 0.0) '(10.0 0.0 0.0) '((8 . "MOBILIER")))
     (tt:line '(0.0 0.0 0.0) '(10.0 10.0 0.0) '((8 . "MURS")))
     (tt:line '(0.0 0.0 0.0) '(0.0 10.0 0.0) '((8 . "0")))
     (tt:block "AVECMOB" (list '((0 . "CIRCLE") (8 . "MOBILIER") (10 0.0 0.0 0.0) (40 . 1.0))
                               '((0 . "LINE") (8 . "0") (10 0.0 0.0 0.0) (11 1.0 0.0 0.0))))
     (tt:insert "AVECMOB" '(50.0 0.0 0.0) nil)
     (tt:run '("CALQUES_SUPPR" "PURGE") '(("CALQUES_FILTRE" "MOB*" "0")))
     (tt:check "objets du calque supprimés" (= 2 (tt:count "LINE")))
     (tt:check "calque 0 protégé" (vl-some '(lambda (d) (= "0" (tp:dxf 8 d))) (tt:of-type "LINE")))
     (tt:check "objets supprimés dans les blocs" (equal (tt:block-types "AVECMOB") '("LINE")))
     (tt:check "calque purgé" (null (tblsearch "LAYER" "MOBILIER")))))

(tt:test "calques caches"
  '(lambda (/ a b c)
     (tt:layer "GELE" 1 1 nil) (tt:layer "ETEINT" -2 0 nil) (tt:layer "VISIBLE" 3 0 nil)
     (setq a (tt:line '(0.0 0.0 0.0) '(1.0 0.0 0.0) '((8 . "GELE"))))
     (setq b (tt:line '(0.0 1.0 0.0) '(1.0 1.0 0.0) '((8 . "ETEINT"))))
     (setq c (tt:line '(0.0 2.0 0.0) '(1.0 2.0 0.0) '((8 . "VISIBLE"))))
     (tt:block "BCACHE" (list '((0 . "CIRCLE") (8 . "GELE") (10 0.0 0.0 0.0) (40 . 1.0))
                              '((0 . "LINE") (8 . "VISIBLE") (10 0.0 0.0 0.0) (11 1.0 0.0 0.0))))
     (tt:insert "BCACHE" '(5.0 0.0 0.0) '((8 . "VISIBLE")))
     (tt:run '("CALQUES_CACHES" "PURGE") '(("GELES") ("DESACTIVES")))
     (tt:check "objets des calques cachés supprimés" (and (null (entget a)) (null (entget b))))
     (tt:check "objets visibles gardés" (entget c))
     (tt:check "objets cachés supprimés dans les blocs" (equal (tt:block-types "BCACHE") '("LINE")))
     (tt:check "calques cachés purgés" (and (null (tblsearch "LAYER" "GELE")) (null (tblsearch "LAYER" "ETEINT"))))))

(tt:test "conversion de calques"
  '(lambda (/ f path e1 e2 e3)
     (setq path (strcat (getenv "TEMP") "\\tp_conv_test.csv"))
     (setq f (open path "w" "utf8"))
     (write-char 65279 f)
     (write-line "Calque source;Calque cible;Couleur;Type de ligne;Epaisseur" f)
     (write-line "MUR*;A-Murs porteurs;1;;0,5" f)
     (write-line "MOB;SUPPRIMER;;;" f)
     (write-line "Été;Hiver;;ACAD_ISO02W100;" f)
     (close f)
     (tt:layer "MUR_EXT" 7 0 nil) (tt:layer "MOB" 7 0 nil) (tt:layer "Été" 7 0 nil)
     (setq e1 (tt:line '(0.0 0.0 0.0) '(10.0 0.0 0.0) '((8 . "MUR_EXT"))))
     (setq e2 (tt:line '(0.0 0.0 0.0) '(10.0 10.0 0.0) '((8 . "MOB"))))
     (setq e3 (tt:line '(0.0 0.0 0.0) '(0.0 10.0 0.0) '((8 . "Été"))))
     (tt:run '("CONV_CALQUES" "PURGE") (list (cons "TABLE_CALQUES" path)))
     (tt:check "objet déplacé sur le calque cible" (= "A-Murs porteurs" (tp:dxf 8 (entget e1))))
     (tt:check "calque cible : couleur et épaisseur" (and (= 1 (tt:layer-color "A-Murs porteurs"))
                                                          (= 50 (tp:dxf 370 (entget (tblobjname "LAYER" "A-Murs porteurs"))))))
     (tt:check "objet du calque SUPPRIMER supprimé" (null (entget e2)))
     (tt:check "accents (CSV UTF-8)" (= "Hiver" (tp:dxf 8 (entget e3))))
     (tt:check "type de ligne chargé pour le calque" (= "ACAD_ISO02W100" (strcase (tp:dxf 6 (tblsearch "LAYER" "Hiver")))))
     (tt:check "calques sources purgés" (and (null (tblsearch "LAYER" "MUR_EXT")) (null (tblsearch "LAYER" "MOB"))))
     ;; table ANSI (Excel « CSV séparateur point-virgule »)
     (setq f (open path "w"))
     (write-line "Été;Automne" f)
     (close f)
     (tt:check "CSV ANSI relu" (equal (car (tp:conv-table path)) '("Été" "Automne" nil nil nil)))
     ;; export
     (tt:check "export de la table" (tp:export-layers path))
     (tt:check "export relu" (vl-some '(lambda (r) (= "A-Murs porteurs" (car r))) (tp:csv-read path)))
     (vl-file-delete path)))

;;; ---------------------------------------------------------------- géométrie

(tt:test "aplatir"
  '(lambda (/ l c p t1 i)
     (setq l (tt:line '(0.0 0.0 5.0) '(10.0 0.0 -3.0) '((39 . 2.0))))
     (entmake '((0 . "CIRCLE") (8 . "0") (10 1.0 2.0 7.0) (40 . 1.0)))
     (setq c (entlast))
     (setq p (tt:lwpoly '((0.0 0.0) (10.0 0.0)) nil '((38 . 4.0))))
     (setq t1 (tt:text "Z" '(0.0 0.0 9.0) nil))
     (tt:block "B3D" (list '((0 . "LINE") (8 . "0") (10 0.0 0.0 3.0) (11 1.0 0.0 3.0))))
     (setq i (tt:insert "B3D" '(5.0 5.0 12.0) nil))
     (tt:run '("APLATIR") nil)
     (tt:check "ligne aplatie" (and (= 0.0 (cadddr (assoc 10 (entget l)))) (= 0.0 (cadddr (assoc 11 (entget l))))))
     (tt:check "épaisseur 0" (member (tp:dxf 39 (entget l)) '(nil 0.0)))
     (tt:check "cercle aplati" (= 0.0 (cadddr (assoc 10 (entget c)))))
     (tt:check "élévation de polyligne 0" (member (tp:dxf 38 (entget p)) '(nil 0.0)))
     (tt:check "texte aplati" (= 0.0 (cadddr (assoc 10 (entget t1)))))
     (tt:check "insertion aplatie" (= 0.0 (cadddr (assoc 10 (entget i)))))
     (tt:check "contenu de bloc aplati" (= 0.0 (cadddr (assoc 10 (car (tt:block-lists "B3D"))))))))

(tt:test "origine et unites"
  '(lambda (/ l)
     (setq l (tt:line '(100.0 200.0 0.0) '(110.0 200.0 0.0) nil))
     (tt:run '("ORIGINE") '(("ORIG_MODE" . "COORD") ("ORIG_PT" 100.0 200.0 0.0)))
     (tt:check "point ramené en 0,0" (tt:near (tp:dxf 10 (entget l)) '(0.0 0.0 0.0)))
     (setvar "INSUNITS" 5)
     (tt:run '("UNITES") '(("UNITE" . 4) ("CONVUNITE" . T) ("UNITE_SRC" . 0) ("PREC" . 1)))
     (tt:check "cm vers mm : × 10" (tt:near (tp:dxf 11 (entget l)) '(100.0 0.0 0.0)))
     (tt:check "unité mm enregistrée" (= 4 (getvar "INSUNITS")))
     (tt:check "précision" (= 1 (getvar "LUPREC")))))

;;; ---------------------------------------------------------------- suppressions

(tt:test "textes"
  '(lambda (/ a b m1 m2)
     (setq a (tt:text "  Salle 12  " '(0.0 0.0 0.0) nil))
     (setq b (tt:text "   " '(0.0 5.0 0.0) nil))
     (setq m1 (tt:mtext "\\P\\PBureau\\P" '(0.0 10.0 0.0) nil))
     (setq m2 (tt:mtext "{\\fArial;  }" '(0.0 15.0 0.0) nil))
     (tt:run '("TEXTES") nil)
     (tt:check "texte rogné" (= "Salle 12" (tp:dxf 1 (entget a))))
     (tt:check "texte vide supprimé" (null (entget b)))
     (tt:check "texte multiligne rogné" (= "Bureau" (tp:mt-get (entget m1))))
     (tt:check "texte multiligne vide supprimé" (null (entget m2)))))

(tt:test "petits objets"
  '(lambda (/ z s k p)
     (setq z (tt:line '(1.0 1.0 0.0) '(1.0 1.0 0.0) nil))
     (setq s (tt:line '(0.0 0.0 0.0) '(0.5 0.0 0.0) nil))
     (setq k (tt:line '(0.0 0.0 0.0) '(5.0 0.0 0.0) nil))
     (setq p (tt:lwpoly '((3.0 3.0) (3.0 3.0)) nil nil))
     (tt:run '("PETITS") '(("TOL" . 0.0)))
     (tt:check "longueur nulle supprimée" (and (null (entget z)) (null (entget p))))
     (tt:check "tolérance 0 : ligne courte gardée" (entget s))
     (tt:run '("PETITS") '(("TOL" . 1.0)))
     (tt:check "tolérance 1 : ligne courte supprimée" (null (entget s)))
     (tt:check "ligne longue gardée" (entget k))))

(tt:test "masques et hachures pleines"
  '(lambda (/ pl w)
     (command "_.WIPEOUT" "0,0" "5,0" "5,5" "")
     (setq w (entlast))
     (setq pl (tt:lwpoly '((10.0 0.0) (20.0 0.0) (20.0 10.0) (10.0 10.0)) T nil))
     (command "_.-HATCH" "_P" "SOLID" "_S" pl "" "") (tp:end-cmd)
     (tt:check "hachure créée" (= 1 (tt:count "HATCH")))
     ;; bloc contenant un masque et une ligne
     (command "_.WIPEOUT" "30,0" "35,0" "35,5" "")
     (tt:line '(30.0 0.0 0.0) '(35.0 5.0 0.0) nil)
     (command "_.-BLOCK" "BMASQUE" "30,0" (entlast) (entnext (entnext pl)) "") (tp:end-cmd)
     (tt:insert "BMASQUE" '(30.0 0.0 0.0) nil)
     (tt:check "bloc avec masque" (member "WIPEOUT" (tt:block-types "BMASQUE")))
     (tt:run '("MASQUES" "HACH_SOLIDES") nil)
     (tt:check "masque supprimé" (null (entget w)))
     (tt:check "hachure pleine supprimée" (= 0 (tt:count "HATCH")))
     (tt:check "masque supprimé du bloc" (equal (tt:block-types "BMASQUE") '("LINE")))
     (tt:check "polyligne gardée" (entget pl))))

(tt:test "groupes, blocs vides, AEC"
  '(lambda (/ a b c d)
     (setq a (tt:line '(0.0 0.0 0.0) '(1.0 0.0 0.0) nil) b (tt:line '(0.0 1.0 0.0) '(1.0 1.0 0.0) nil)
           c (tt:line '(0.0 2.0 0.0) '(1.0 2.0 0.0) nil))
     (command "_.-GROUP" "_C" "SEUL" "" a "") (tp:end-cmd)
     (command "_.-GROUP" "_C" "DEUX" "" b c "") (tp:end-cmd)
     (tt:block "VIDE" nil)
     (tt:insert "VIDE" '(0.0 0.0 0.0) nil)
     (regapp "AEC_TEST")
     (setq d (tt:line '(0.0 3.0 0.0) '(1.0 3.0 0.0) '((-3 ("AEC_TEST" (1000 . "x"))))))
     (dictadd (namedobjdict) "AEC_ESSAI" (entmakex '((0 . "DICTIONARY") (100 . "AcDbDictionary"))))
     (tt:run '("GROUPES" "BLOCS_VIDES" "PROXY" "PURGE") nil)
     (setq gd (dictsearch (namedobjdict) "ACAD_GROUP"))
     (tt:check "groupe d'un objet supprimé" (not (member '(3 . "SEUL") gd)))
     (tt:check "groupe de deux objets gardé" (member '(3 . "DEUX") gd))
     (tt:check "référence de bloc vide supprimée" (= 0 (tt:count "INSERT")))
     (tt:check "bloc vide purgé" (null (tblsearch "BLOCK" "VIDE")))
     (tt:check "données étendues AEC retirées" (null (assoc -3 (entget d '("AEC*")))))
     (tt:check "dictionnaire AEC supprimé" (null (dictsearch (namedobjdict) "AEC_ESSAI")))))

(tt:test "presentations et xrefs"
  '(lambda (/ path)
     (command "_.-LAYOUT" "_N" "Essai") (tp:end-cmd)
     (setq path (strcat (getenv "TEMP") "\\tp_xref_test.dwg"))
     (if (findfile path) (vl-file-delete path))
     (tt:line '(0.0 0.0 0.0) '(1.0 1.0 0.0) nil)
     (command "_.-WBLOCK" path "" "0,0" (entlast) "") (tp:end-cmd)
     (command "_.-XREF" "_A" path "0,0" 1 1 0) (tp:end-cmd)
     (tt:check "xref attachée" (tblsearch "BLOCK" "tp_xref_test"))
     (entdel (entlast))
     (tt:run '("PRESENTATIONS" "XREFS") '(("XREF_MODE" . "NONREF")))
     (tt:check "présentation supprimée" (not (member "Essai" (tp:layout-names))))
     (tt:check "xref non référencée détachée" (null (tblsearch "BLOCK" "tp_xref_test")))
     (vl-file-delete path)))

;;; ---------------------------------------------------------------- normalisation

(tt:test "couleurs"
  '(lambda (/ a b c i)
     (tt:layer "ROUGE" 1 0 nil)
     (setq a (tt:line '(0.0 0.0 0.0) '(1.0 0.0 0.0) '((62 . 1))))
     (setq b (tt:line '(0.0 1.0 0.0) '(1.0 1.0 0.0) '((62 . 5) (420 . 16711680))))
     (tt:block "BCOUL" (list '((0 . "LINE") (8 . "0") (62 . 3) (10 0.0 0.0 0.0) (11 1.0 0.0 0.0))))
     (setq i (tt:insert "BCOUL" '(0.0 0.0 0.0) nil))
     (tt:run '("DUCALQUE" "DUBLOC") nil)
     (tt:check "couleur DuCalque" (null (tp:dxf 62 (entget a))))
     (tt:check "couleur vraie retirée" (and (null (tp:dxf 62 (entget b))) (null (tp:dxf 420 (entget b)))))
     (tt:check "composant de bloc DuBloc" (= 0 (tp:dxf 62 (car (tt:block-lists "BCOUL")))))
     ;; table de conversion
     (setq c (tt:line '(0.0 2.0 0.0) '(1.0 2.0 0.0) '((62 . 1))))
     (setq a (tt:line '(0.0 3.0 0.0) '(1.0 3.0 0.0) '((8 . "ROUGE"))))
     (tt:run '("COULEURS") '(("COUL_TABLE" (1 . 3)) ("COUL_CALQUES" . T) ("COUL_FORCEES" . T) ("COUL_DUCALQUE")))
     (tt:check "couleur forcée convertie" (= 3 (tp:dxf 62 (entget c))))
     (tt:check "couleur de calque convertie" (= 3 (tt:layer-color "ROUGE")))
     (tt:check "objet DuCalque inchangé" (null (tp:dxf 62 (entget a))))
     (tt:layer "BLEU" 5 0 nil)
     (setq a (tt:line '(0.0 4.0 0.0) '(1.0 4.0 0.0) '((8 . "BLEU"))))
     (tt:run '("COULEURS") '(("COUL_TABLE" (5 . 2)) ("COUL_CALQUES") ("COUL_FORCEES") ("COUL_DUCALQUE" . T)))
     (tt:check "objet DuCalque forcé d'après son calque" (= 2 (tp:dxf 62 (entget a))))
     (tt:run '("COULEUR_UNIQUE") '(("COUL_UNIQUE" . 8) ("CU_CALQUES" . T) ("CU_ENTITES")))
     (tt:check "couleur unique des calques" (and (= 8 (tt:layer-color "ROUGE")) (= 8 (tt:layer-color "BLEU")) (= 8 (tt:layer-color "0"))))))

(tt:test "types et epaisseurs de ligne"
  '(lambda (/ a b)
     (tp:ensure-ltype "ACAD_ISO02W100")
     (setq a (tt:line '(0.0 0.0 0.0) '(1.0 0.0 0.0) '((6 . "ACAD_ISO02W100") (48 . 3.0))))
     (setq b (tt:line '(0.0 1.0 0.0) '(1.0 1.0 0.0) '((370 . 50))))
     (tt:run '("TYPESLIGNE") '(("TL_TABLE" ("ACAD_ISO02W100" . "ACAD_ISO03W100")) ("TL_ECHELLE1" . T)))
     (tt:check "type de ligne converti" (= "ACAD_ISO03W100" (strcase (tp:dxf 6 (entget a)))))
     (tt:check "échelle de type de ligne 1" (member (tp:dxf 48 (entget a)) '(nil 1.0)))
     (tt:run '("TL_DUCALQUE" "EP_DUCALQUE") nil)
     (tt:check "type de ligne DuCalque" (member (tp:dxf 6 (entget a)) '(nil "ByLayer" "BYLAYER")))
     (tt:check "épaisseur DuCalque" (member (tp:dxf 370 (entget b)) '(nil -1)))))

(tt:test "styles et textes multilignes"
  '(lambda (/ a m d)
     (entmake '((0 . "STYLE") (100 . "AcDbSymbolTableRecord") (100 . "AcDbTextStyleTableRecord") (2 . "AUTRE")
                (70 . 0) (40 . 0.0) (41 . 1.0) (50 . 0.0) (71 . 0) (42 . 2.5) (3 . "romans.shx") (4 . "")))
     (setq a (tt:text "A" '(0.0 0.0 0.0) '((7 . "AUTRE"))))
     (setq m (tt:mtext "{\\C1;\\fArial|b1;\\H2x;Bonjour}\\L\\Pmonde" '(0.0 5.0 0.0) '((90 . 1) (63 . 7) (45 . 1.5))))
     (tt:run '("STYLES" "MTEXT" "PURGE") '(("STYLE_NOM" . "Standard") ("POLICE" . "arial.ttf")))
     (tt:check "style fusionné" (= "STANDARD" (strcase (tp:dxf 7 (entget a)))))
     (tt:check "style inutilisé purgé" (null (tblsearch "STYLE" "AUTRE")))
     (tt:check "police remplacée" (= "ARIAL.TTF" (strcase (tp:dxf 3 (tblsearch "STYLE" "Standard")))))
     (setq m (car (tt:of-type "MTEXT")))
     (tt:check "couleur, police, souligné retirés ; hauteur gardée" (= "{\\H2x;Bonjour}\\Pmonde" (tp:mt-get m)))
     (tt:check "masque d'arrière-plan retiré" (member (tp:dxf 90 m) '(nil 0)))
     (tt:check "texte multiligne recréé une seule fois" (= 1 (tt:count "MTEXT")))))

(tt:test "cotes et hachures"
  '(lambda (/ dim h pl)
     (setvar "DIMCLRD" 1)
     (command "_.-DIMSTYLE" "_S" (getvar "DIMSTYLE") "_Y") (tp:end-cmd)
     (command "_.DIMLINEAR" "0,0" "100,0" "50,20") (tp:end-cmd)
     (setq dim (entlast))
     (setq pl (tt:lwpoly '((0.0 0.0) (10.0 0.0) (10.0 10.0)) T nil))
     (command "_.-HATCH" "_P" "ANSI31" "" "" "_S" pl "" "") (tp:end-cmd)
     (setq h (entlast))
     (tt:run '("COTES_CALQUE" "HACH_CALQUE" "COTES_DUBLOC" "HACH_ARRIERE") nil)
     (tt:check "cote sur le calque COTES" (= "COTES" (tp:dxf 8 (entget dim))))
     (tt:check "hachure sur le calque HACHURES" (= "HACHURES" (tp:dxf 8 (entget h))))
     (command "_.-DIMSTYLE" "_R" (getvar "DIMSTYLE")) (tp:end-cmd)
     (tt:check "style de cote DuBloc" (= 0 (getvar "DIMCLRD")))))

;;; ---------------------------------------------------------------- blocs imbriqués

(tt:test "blocs imbriques"
  '(lambda (/ lists types circ txt el)
     (tt:layer "X" 7 0 nil)
     (tt:block "ENFANT" (list '((0 . "CIRCLE") (8 . "0") (62 . 0) (10 0.0 0.0 0.0) (40 . 1.0))
                              '((0 . "ARC") (8 . "0") (10 0.0 0.0 0.0) (40 . 2.0) (50 . 0.0) (51 . 1.0))
                              '((0 . "ATTDEF") (8 . "0") (10 0.0 0.0 0.0) (40 . 1.0) (1 . "D") (3 . "Num") (2 . "NUM") (70 . 0))))
     (tt:block "PARENT" (list '((0 . "LINE") (8 . "0") (10 0.0 0.0 0.0) (11 10.0 0.0 0.0))
                              '((0 . "INSERT") (2 . "ENFANT") (8 . "X") (62 . 5) (66 . 1) (10 5.0 5.0 0.0) (41 . 2.0) (42 . 1.0) (43 . 1.0))
                              '((0 . "ATTRIB") (8 . "0") (10 5.0 6.0 0.0) (40 . 1.0) (1 . "B12") (2 . "NUM") (70 . 0))
                              '((0 . "SEQEND") (8 . "0"))))
     (tt:insert "PARENT" '(0.0 0.0 0.0) nil)
     (tt:run '("NEXPL") nil)
     (setq lists (tt:block-lists "PARENT") types (mapcar '(lambda (d) (tp:dxf 0 d)) lists))
     (tt:check "plus de référence imbriquée" (not (member "INSERT" types)))
     (setq circ (vl-some '(lambda (d) (if (member (tp:dxf 0 d) '("CIRCLE" "ELLIPSE")) d)) lists))
     (tt:check "cercle décomposé (échelle 2 x 1 : ellipse)" (= "ELLIPSE" (tp:dxf 0 circ)))
     (tt:check "calque 0 -> calque de la référence" (= "X" (tp:dxf 8 circ)))
     (tt:check "DuBloc -> couleur de la référence" (= 5 (tp:dxf 62 circ)))
     (setq txt (vl-some '(lambda (d) (if (= "TEXT" (tp:dxf 0 d)) d)) lists))
     (tt:check "attribut -> texte avec sa valeur" (and txt (= "B12" (tp:dxf 1 txt))))
     (tt:check "pas de définition d'attribut ajoutée" (not (member "ATTDEF" types)))
     (tt:check "ligne du parent gardée" (member "LINE" types))
     (tt:check "aucun reste dans l'espace objet" (= 1 (length (tt:all))))))

;;; ---------------------------------------------------------------- finition et annulation

(tt:test "purge, echelles, annulation"
  '(lambda (/ n)
     (tt:layer "INUTILE" 3 0 nil)
     (tt:line '(0.0 0.0 0.0) '(5.0 0.0 0.0) nil)
     (tt:run '("PURGE" "ECHELLES" "AUDIT") nil)
     (tt:line '(0.0 0.0 0.0) '(0.0 0.0 0.0) nil)
     (tt:check "calque inutilisé purgé" (null (tblsearch "LAYER" "INUTILE")))
     (tt:check "liste d'échelles normalisée"
               (vl-some '(lambda (p) (and (= 350 (car p)) (= "1:50" (tp:dxf 300 (entget (cdr p))))))
                        (dictsearch (namedobjdict) "ACAD_SCALELIST")))
     (setq n (length (tt:all)))
     (tt:run '("PETITS") nil)
     (tt:check "petit objet supprimé" (= (1- n) (length (tt:all))))
     (command "_.U")
     (tt:check "un seul U annule le traitement" (= n (length (tt:all))))))

(tt:test "import PDF, couleur forcee unique"
  '(lambda (/ pl1 pl2 a i)
     (tt:layer "PDF_Remplissages" 7 0 nil)
     (setq pl1 (tt:lwpoly '((0.0 0.0) (1.0 0.0) (1.0 1.0)) T '((8 . "PDF_Remplissages"))))
     (command "_.-HATCH" "_P" "SOLID" "_S" pl1 "" "") (tp:end-cmd)
     (entmod (tp:put 8 "PDF_Remplissages" (entget (entlast))))
     (setq pl2 (tt:lwpoly '((5.0 0.0) (6.0 0.0) (6.0 1.0)) T nil))
     (command "_.-HATCH" "_P" "SOLID" "_S" pl2 "" "") (tp:end-cmd)
     (tt:run '("HACH_SOLIDES") nil)
     (tt:check "hachure pleine d'import PDF gardée" (= 1 (tt:count "HATCH")))
     (tt:check "avertissement import PDF" (vl-some '(lambda (l) (wcmatch l "*import PDF*")) tt:*report*))
     (setq a (tt:line '(0.0 5.0 0.0) '(1.0 5.0 0.0) '((62 . 1))))
     (tt:block "BUNI" (list '((0 . "LINE") (8 . "0") (62 . 3) (10 0.0 0.0 0.0) (11 1.0 0.0 0.0))))
     (setq i (tt:insert "BUNI" '(0.0 0.0 0.0) nil))
     (tt:run '("COULEUR_UNIQUE") '(("COUL_UNIQUE" . 8) ("CU_CALQUES") ("CU_ENTITES" . T)))
     (tt:check "objet forcé en couleur unique" (= 8 (tp:dxf 62 (entget a))))
     (tt:check "composant de bloc DuBloc" (= 0 (tp:dxf 62 (car (tt:block-lists "BUNI")))))))

(tt:test "xrefs liees"
  '(lambda (/ path)
     (setq path (strcat (getenv "TEMP") "\\tp_xref_lier.dwg"))
     (if (findfile path) (vl-file-delete path))
     (tt:line '(0.0 0.0 0.0) '(1.0 1.0 0.0) nil)
     (command "_.-WBLOCK" path "" "0,0" (entlast) "") (tp:end-cmd)
     (command "_.-XREF" "_A" path "0,0" 1 1 0) (tp:end-cmd)
     (tt:run '("XREFS") '(("XREF_MODE" . "LIER") ("IMAGE_MODE" . "AUCUNE")))
     (tt:check "xref liée : bloc ordinaire" (and (tblsearch "BLOCK" "tp_xref_lier")
                                                 (= 0 (logand 4 (tp:dxf 70 (tblsearch "BLOCK" "tp_xref_lier"))))))
     (tt:check "rapport : xref liée" (vl-some '(lambda (l) (wcmatch l "*liées*")) tt:*report*))
     (vl-file-delete path)))

;; En dernier : le traitement par lot enregistre le dessin sous un autre nom.
(tt:test "traitement par lot"
  '(lambda (/ out log f lines)
     (setq out (strcat (getenv "TEMP") "\\tp_lot_sortie") log (strcat out "\\rapport.txt"))
     (vl-mkdir out)
     (foreach x (vl-directory-files out "*.*" 1) (vl-file-delete (strcat out "\\" x)))
     (tp:profile-write "Lot" (tt:cfg '("PETITS") nil))
     (tt:line '(1.0 1.0 0.0) '(1.0 1.0 0.0) nil)
     (tt:line '(0.0 0.0 0.0) '(5.0 0.0 0.0) nil)
     (setq name (getvar "DWGNAME"))
     (tp:batch-one "Lot" out log)
     (tt:check "dessin traité enregistré dans le dossier de sortie" (findfile (strcat out "\\" name)))
     (tt:check "objet nul supprimé avant enregistrement" (= 1 (tt:count "LINE")))
     (setq lines (tp:read-lines log "utf8"))
     (tt:check "rapport du lot écrit" (and lines (wcmatch (car lines) "== *")))))

(princ (strcat "\nCV-RES=BILAN " (itoa tt:*ok*) " OK, " (itoa tt:*ko*) " ECHEC"))
(princ)
